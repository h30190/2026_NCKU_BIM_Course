; Read-only ModelSpace export for AutoCAD Core Console. No SAVE commands.
(vl-load-com)
(defun ck-clean (s) (if s (vl-string-translate "\t\r\n" "   " s) ""))
(defun ck-n (n) (rtos n 2 10))
(defun ck-join (lst sep / r) (setq r "") (foreach s lst (setq r (strcat r (if (= r "") "" sep) s))) r)
(defun ck-xyz (p) (strcat (ck-n (car p)) "," (ck-n (cadr p)) "," (ck-n (if (caddr p) (caddr p) 0.0))))
(defun ck-points (en d / ty a b step k p out bulged)
  (setq ty (cdr (assoc 0 d)) out nil)
  (cond
    ((member ty '("POINT" "TEXT" "MTEXT" "INSERT"))
      (if (assoc 10 d) (setq out (list (trans (cdr (assoc 10 d)) en 0)))))
    ((member ty '("LINE" "LWPOLYLINE" "POLYLINE" "ARC" "CIRCLE" "ELLIPSE" "SPLINE"))
      (if (not (and (= ty "POLYLINE") (/= 0 (logand 80 (cdr (assoc 70 d))))))
        (progn
          (setq a (vlax-curve-getStartParam en) b (vlax-curve-getEndParam en))
          (cond
            ((= ty "LINE") (setq step (- b a)))
            ((member ty '("LWPOLYLINE" "POLYLINE"))
              (setq bulged nil)
              (foreach pair d (if (and (= (car pair) 42) (/= (cdr pair) 0.0)) (setq bulged T)))
              ; old POLYLINE arcs may store bulges on vertices; subdivide conservatively.
              (setq step (if (or bulged (= ty "POLYLINE")) 0.125 1.0)))
            (T (setq step (/ (- b a) 128.0))))
          (if (> step 0)
            (progn
              (setq k a)
              (while (and (< k b) (< (length out) 25000))
                (setq p (vlax-curve-getPointAtParam en k))
                (if p (setq out (cons p out)))
                (setq k (+ k step)))
              (setq p (vlax-curve-getPointAtParam en b))
              (if p (setq out (cons p out)))
              (setq out (reverse out))))))))
  out)
(defun ck-export (target / f ss i en d ty layer text pts outcome closed)
  (setq f (open target "w"))
  (write-line (strcat "UNITS\t" (itoa (getvar "INSUNITS"))) f)
  (setq ss (ssget "_X" '((410 . "Model"))))
  (if ss
    (progn (setq i 0)
      (repeat (sslength ss)
        (setq en (ssname ss i) d (entget en) ty (cdr (assoc 0 d)) layer (cdr (assoc 8 d)))
        (setq text "")
        (foreach pair d (if (= (car pair) 3) (setq text (strcat text (cdr pair)))))
        (if (assoc 1 d) (setq text (strcat text (cdr (assoc 1 d)))))
        (setq outcome (vl-catch-all-apply 'ck-points (list en d)))
        (setq pts (if (vl-catch-all-error-p outcome) nil outcome))
        (setq closed (if (or (= ty "CIRCLE") (and (assoc 70 d) (/= 0 (logand 1 (cdr (assoc 70 d)))))) "1" "0"))
        (write-line (ck-join (list (cdr (assoc 5 d)) ty (ck-clean layer) (ck-clean text) closed
          (ck-join (mapcar 'ck-xyz pts) ";") (if (vl-catch-all-error-p outcome) "geometry_error" "ok")) "\t") f)
        (setq i (1+ i)))))
  (close f) (princ))
